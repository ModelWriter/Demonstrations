# Specification: Document

## 1: Introduction

### 1.1: Purpose

### 1.2: Definitions

### 1.3: Nomenclature/Abbreviation

#### 1.3.1: 1
A/C	Aircraft

#### 1.3.2: 2
ATA	Air Transport Association

### 1.4: Document Precedence

## 2: Objectives

## 3: Reference Regulations/Documents

### 3.1: Airworthiness Regulations

#### 3.1.1: 1
JAR 25.607	Fasteners

#### 3.1.2: 2
REF	Title

### 3.2: Others

#### 3.2.1: 1
A350XWB_SIDP V&V Policy 	PL0901917

## 4: Responsibilities

## 5: Structures/Systems Configuration

## 6: Application Domain

## 7: Design Principles

### 7.1: Design Principles Applicable to the Entire Design

#### 7.1.1: General

#### 7.1.2: SIDP92A001V-A-269

#### 7.1.3: SIDP92A001V-A-280

#### 7.1.4: SIDP92A001V-A-356

##### 7.1.4.1: Locking Of Bolted Fastenings

#### 7.1.5: SIDP92A001V-A-413

#### 7.1.6: SIDP92A001V-A-424

##### 7.1.6.1: Installation In Ceiling Area

#### 7.1.7: SIDP92A001V-A-3763

##### 7.1.7.1: Installation In Fuel Tanks

#### 7.1.8: SIDP92A001V-A-472

#### 7.1.9: Positioning of Bundles in the Aircraft Considering Environmental Constraints

##### 7.1.9.1: General

##### 7.1.9.2: SIDP92A001V-A-557

##### 7.1.9.3: SIDP92A001V-A-579

#### 7.1.10: Segregation or Clearances of Bundles to A/C Structure, other Systems or Between Routes

##### 7.1.10.1: General Applications

###### 7.1.10.1.1: Sagging (s)

###### 7.1.10.1.2: SIDP92A001V-A-784

##### 7.1.10.2: Clearance Values between Bundles and A/C Structure or other Systems

##### 7.1.10.3: Clearances Values between Bundles

### 7.2: Installation of Connection Elements and Feed Through Seals

#### 7.2.1: Positioning and Selection of Connection Elements/Feed through Seals in the Aircraft Considering Environmental Constraints

#### 7.2.2: Attachment of Connections Elements/Feed through Seals to A/C Structure

### 7.3: Installation of Electrical Equipment

#### 7.3.1: Positioning of Electrical Equipment in the Aircraft Considering Environmental Constraints

## 8: Approval Sheet

## 9: Record of Revisions

## 10: Appendices

### 10.1: Appendix A. Electrical Bundles Weight

### 10.2: Appendix B. List of Approved Material, Standard Parts and Processes Prescribed

### 10.3: Appendix C. Clamp Size

### 10.4: Appendix D. List of VU

### 10.5: Appendix E. Loss of Attachment Point

#### 10.5.1: Appendix E. Loss of Attachment Point

### 10.6: Appendix F. Mandatory Design Principles
